// requirement・requirement-name-compartment・distinguished-parameter・subject・actor・stakeholder・subject-name・actor-name・
// stakeholder-name・distinguished-parameter-link・subject-actors-stakeholders-node・frames-compartment・
// assume-constraints-compartment・require-constraints-compartment・constraints-compartment・concerns-compartment・
// requirements-compartment
part def P {
    requirement r {
        subject s;
        actor u;
        stakeholder k;
        frame cc;
        assume constraint c1;
        require constraint c2;
        constraint c3;
        concern c4;
        requirement r2;
    }
    part q;
}
